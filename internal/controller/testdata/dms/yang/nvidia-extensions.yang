// Copyright 2026 NVIDIA CORPORATION & AFFILIATES
module nvidia-extensions {
  yang-version 1.1;
  namespace "urn:dms-lib:test:extensions";
  prefix ext;
  import nvidia-root { prefix nv; }
  augment "/nv:nvidia" {
    container nvconfig {
      action apply {
        input { leaf force { type boolean; } }
        output { leaf status { type string; } }
      }
    }
    container raw {
      container nvconfig {
        action query {
          input { leaf type { type string; } }
          output { leaf status { type string; } }
        }
      }
    }
  }
}
